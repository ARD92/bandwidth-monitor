/*
Version: V1.0
Date: 2022-11-03
Description: Optional yang package to view peak BW utilized every month
*/

module bandwidth-account {
	namespace "http://bandwidth-account";
	prefix "bandwidth-account";
	import junos-extension {
		prefix junos;
	}
	import junos-extension-odl {
		prefix junos-odl;
	}
	organization "Juniper Networks";
	contact "Aravind Prabhakar";
	description "yang model to view bandwidth accounted 
		    for every month";
	revision "2022-11-03" {
		description "Version 1.0";
	}
	rpc get-bandwidth-account {
		description "rpc to display peak BW utilized over the month";
		junos:command "show bandwidth-account" {
			junos:action-execute {
				junos:script "bw_account_action.py";
			}
		}
		input {
			leaf month {
				type string;
				description "3 letter month format. eg jan,feb.. ";
			}
			leaf year {
				type string;
				description "4 digit year representation";
			}
			leaf detail {
				type empty;
				description "detailed view of bps across all monitored interfaces";
			}
		}
		output {
			container bw-account {
				leaf time {
					type string;
				}
				leaf interface {
					type string;
				}
				leaf peak-bps {
					type string;
				}
				leaf intf-peak-bps {
					type string;
				}
				container bandwidth-account-format {
			 		junos-odl:cli-format;
					junos-odl:header "Bandwidth accounting information\n";
					junos-odl:picture '
	time	      : @<<<<<<<<<<<<<<<<<<<<<<<
	interface     : @<<<<<<<<<<<<<<<<<<<<<<<
	peak-bps      : @<<<<<<<<<<<<<<<<<<<<<<<
	intf-peak-bps : @<<<<<<<<<<<<<<<<<<<<<<<';
				junos-odl:line {
					junos-odl:field "time";
				}	
				junos-odl:line {
					junos-odl:field "interface";
				}
				junos-odl:line {
					junos-odl:field "peak-bps";
				}
				junos-odl:line {
					junos-odl:field "intf-peak-bps";
				}
				junos-odl:blank-line;
				}
			}
		}
	}
}
