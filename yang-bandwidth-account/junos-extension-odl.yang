/*
 * Copyright (c) 2016 Juniper Networks, Inc.
 * All rights reserved.
 */

module junos-extension-odl {
  namespace "http://yang.juniper.net/yang/1.1/jodl";
  prefix odl;

  organization "Juniper Networks, Inc.";

  description "This module contains definitions for Junos YANG ODL extensions.";

  extension header {
    argument "header";
    description "ODL format header";
  }
  extension header-group {
    argument "header-group";
    description "ODL format header group";
  }
  extension picture {
    argument "picture";
    description "ODL format picture";
  }
  extension line {
    description "ODL line statement";
  }
  extension field {
    argument "field";
    description "ODL field statement";
  }
  extension help {
    argument "help";
    description "ODL tag help";
  }
  extension style {
    argument "style";
    description "ODL format style";
  }
  extension template {
    argument "template";
    description "ODL format template";
  }
  extension seconds {
    argument "seconds";
    description "ODL format date";
  }
  extension missing {
    argument "missing";
    description "Text to display when container tag is missing";
  }
  extension indent {
    argument "indent";
    description "Indent the display to right";
  }
  extension default-text {
    argument "default-text";
    description "ODL default text for missing field";
  }
  extension formal-name {
    argument "formal-name";
    description "ODL formal name for rendering";
  }
  extension format {
    argument "format";
  }
  extension cli-format {
    description "Flag for container used for cli rendering";
  }
  /* Flags */
  extension truncate {
    description "ODL flag for truncate";
  }
  extension comma {
    description "ODL flag for comma";
  }
  extension space {
    description "ODL flag for space";
  }
  extension colon {
    description "ODL flag for colon";
  }
  extension once {
    description "ODL flag for once";
  }
  extension flush {
    description "ODL flag for flush";
  }
  extension wordwrap {
    description "ODL flag for wordwrap";
  }
  extension fieldwrap {
    description "ODL flag for fieldwrap";
  }
  extension reset {
    description "ODL flag for reset";
  }
  extension explicit {
    description "ODL flag for explicit";
  }
  extension leading {
    description "ODL flag for leading";
  }
  extension preserve {
    description "ODL flag for preserve";
  }
  extension capitalize {
    description "ODL flag to capitalize the text output";
  }
  extension float {
    description "ODL flag for float";
  }
  extension resolvable {
    description "ODL flag for resolvable";
  }
  extension emit {
    description "ODL flag for emit";
  }
  extension chevrons {
    description "ODL flag for chevrons";
  }
  extension parentheses {
    description "ODL flag for parentheses";
  }
  extension complete {
    description "ODL flag for complete";
  }
  extension state {
    description "ODL flag for state";
  }
  extension date-time {
    description "ODL flag for date-time";
  }
  extension identifier {
    description "ODL flag for identifier";
  }
  /* Format Flags */
  extension no-linebreak {
    description "ODL format flag for no linebreak";
  }
  extension blank-line {
    description "ODL format flag to emit newline before format except first time";
  }
}
